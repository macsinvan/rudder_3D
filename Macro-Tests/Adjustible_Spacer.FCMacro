# -*- coding: utf-8 -*-
"""
TableLegLeveler_FINAL.py
Clean version using FSThreadedRod from your macro
"""

import FreeCAD
import FreeCADGui
from PySide import QtGui, QtCore
import Part

class LevelerBase(QtGui.QDialog):
    def __init__(self):
        super(LevelerBase, self).__init__()
        self.initUI()
        
    def initUI(self):
        self.setWindowTitle("Table Leg Leveler - FINAL")
        self.setMinimumWidth(400)
        
        layout = QtGui.QVBoxLayout()
        
        # Title
        title = QtGui.QLabel("<h2>Table Leg Leveler Base</h2>")
        title.setAlignment(QtCore.Qt.AlignCenter)
        layout.addWidget(title)
        
        # Info
        info = QtGui.QLabel("Creates base with FSThreadedRod")
        info.setAlignment(QtCore.Qt.AlignCenter)
        layout.addWidget(info)
        
        # Parameters
        params = QtGui.QGroupBox("Dimensions (mm)")
        form = QtGui.QFormLayout()
        
        self.base_d = QtGui.QDoubleSpinBox()
        self.base_d.setRange(10, 100)
        self.base_d.setValue(27)
        form.addRow("Base Diameter:", self.base_d)
        
        self.base_h = QtGui.QDoubleSpinBox()
        self.base_h.setRange(3, 20)
        self.base_h.setValue(5)
        form.addRow("Base Height:", self.base_h)
        
        self.thread_d = QtGui.QDoubleSpinBox()
        self.thread_d.setRange(10, 50)
        self.thread_d.setValue(26)
        form.addRow("Thread Diameter:", self.thread_d)
        
        self.thread_l = QtGui.QDoubleSpinBox()
        self.thread_l.setRange(10, 100)
        self.thread_l.setValue(25)
        form.addRow("Thread Length:", self.thread_l)
        
        params.setLayout(form)
        layout.addWidget(params)
        
        # Status
        self.status = QtGui.QLabel("")
        self.status.setWordWrap(True)
        self.status.setMinimumHeight(50)
        layout.addWidget(self.status)
        
        # Create button
        create_btn = QtGui.QPushButton("CREATE BASE")
        create_btn.clicked.connect(self.createBase)
        create_btn.setMinimumHeight(35)
        create_btn.setStyleSheet("""
            QPushButton {
                background-color: #4CAF50;
                color: white;
                font-weight: bold;
                font-size: 14px;
            }
        """)
        layout.addWidget(create_btn)
        
        self.setLayout(layout)
    
    def createBase(self):
        """Create base with threaded rod"""
        self.status.setText("Creating...")
        QtGui.QApplication.processEvents()
        
        base_diameter = self.base_d.value()
        base_height = self.base_h.value()
        thread_diameter = self.thread_d.value()
        thread_length = self.thread_l.value()
        
        try:
            # Create or get document
            if not FreeCAD.ActiveDocument:
                FreeCAD.newDocument("LegLeveler")
            doc = FreeCAD.ActiveDocument
            
            # Activate Fasteners Workbench
            FreeCADGui.activateWorkbench('FastenersWorkbench')
            
            # 1. Create base cylinder
            base = Part.makeCylinder(
                base_diameter/2,
                base_height,
                FreeCAD.Vector(0, 0, 0),
                FreeCAD.Vector(0, 0, 1)
            )
            base_obj = doc.addObject("Part::Feature", "BaseCylinder")
            base_obj.Shape = base
            
            # 2. Create threaded rod
            # Use the exact sequence from your macro
            FreeCADGui.runCommand('FSThreadedRod', 0)
            
            # Get the created object (should be the last one)
            # Wait a moment for it to be created
            doc.recompute()
            
            # Find the threaded rod object
            thread_obj = None
            for obj in doc.Objects:
                if 'ThreadedRod' in obj.Name or 'Screw' in obj.Name:
                    thread_obj = obj
                    break
            
            if not thread_obj:
                # Get the last created object
                thread_obj = doc.Objects[-1]
            
            # 3. Configure the threaded rod (exact sequence from your macro)
            thread_obj.Diameter = "Custom"
            doc.recompute()
            
            thread_obj.DiameterCustom = f'{thread_diameter} mm'
            doc.recompute()
            
            thread_obj.Thread = True
            
            # Set length if property exists
            if hasattr(thread_obj, 'Length'):
                thread_obj.Length = f'{thread_length} mm'
            
            # Position on top of base
            thread_obj.Placement.Base = FreeCAD.Vector(0, 0, base_height)
            
            # 4. Combine parts
            fusion = doc.addObject("Part::MultiFuse", "LevelerBase")
            fusion.Shapes = [base_obj, thread_obj]
            
            base_obj.ViewObject.Visibility = False
            thread_obj.ViewObject.Visibility = False
            
            doc.recompute()
            
            # Set view
            FreeCADGui.activeDocument().activeView().viewAxonometric()
            FreeCADGui.SendMsgToActiveView("ViewFit")
            
            self.status.setText("✅ Success! Base created with threaded rod")
            
        except Exception as e:
            self.status.setText(f"Error: {str(e)}")
            print(f"Error details: {e}")
            import traceback
            traceback.print_exc()

def main():
    dialog = LevelerBase()
    dialog.exec_()

if __name__ == "__main__":
    main()
