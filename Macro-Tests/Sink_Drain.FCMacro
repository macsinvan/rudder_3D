#!/usr/bin/env python3
# -*- coding: utf-8 -*-
"""
FreeCAD 1.0 Script - FINAL DRAIN BASIN - WORKING VERSION
- 80mm deep
- 4mm holes, 16mm spacing (optimized for export)
- CORRECT corner coverage (all corners have drainage)
- 2mm wall thickness
- Top flange (10mm wide, 4mm thick)
"""

import FreeCAD
import Part
import math

# Parameters
wall_depth = 80.0          # mm - basin depth
wall_thickness = 2.0       # mm
flange_width = 10.0       # mm - extends outward
flange_thickness = 4.0    # mm
length = 395.0            # mm - outer length
width = 250.0             # mm - outer width  
corner_radius = 75.0      # mm

# OPTIMIZED HOLE PARAMETERS (user's solution)
hole_diameter = 4.0       # mm - larger holes
hole_spacing = 16.0       # mm - wider spacing for faster export

bottom_fillet = 2.0       # mm - bottom edge fillet

print("="*60)
print("FINAL DRAIN BASIN - 80mm WITH OPTIMIZED MESH")
print("="*60)

# Create or get document
doc = FreeCAD.newDocument("DrainBasin80mm_Final") if not FreeCAD.ActiveDocument else FreeCAD.ActiveDocument

# Clear existing objects
for obj in doc.Objects:
    doc.removeObject(obj.Name)

print("\n[1/5] Creating base profile...")

# Create rounded rectangle profile
profile = Part.makeBox(length, width, 1, FreeCAD.Vector(0, 0, 0))
edges_to_fillet = []
for i, edge in enumerate(profile.Edges):
    if abs(edge.Curve.Direction.z) > 0.99:  # Vertical edges
        edges_to_fillet.append((i+1, corner_radius, corner_radius))
        
if edges_to_fillet:
    profile = profile.makeFillet(corner_radius, [profile.Edges[i[0]-1] for i in edges_to_fillet])

# Get the profile face
profile_face = None
for face in profile.Faces:
    if abs(face.CenterOfMass.z) < 0.1:
        profile_face = face
        break

print("✓ Profile created: {}mm x {}mm with {}mm radius corners".format(length, width, corner_radius))

print("\n[2/5] Extruding and hollowing basin...")

# Extrude to create solid
solid_basin = profile_face.extrude(FreeCAD.Vector(0, 0, -wall_depth))

# Hollow out using thickness operation
top_face = None
for face in solid_basin.Faces:
    if abs(face.CenterOfMass.z) < 0.1 and abs(face.normalAt(0,0).z - 1) < 0.1:
        top_face = face
        break

hollow_basin = solid_basin.makeThickness([top_face], -wall_thickness, 1e-6)
print("✓ Basin hollowed: {}mm deep, {}mm wall thickness".format(wall_depth, wall_thickness))

print("\n[3/5] Adding top flange...")

# Create flange outer profile
flange_outer = Part.makeBox(
    length + 2*flange_width, 
    width + 2*flange_width, 
    flange_thickness,
    FreeCAD.Vector(-flange_width, -flange_width, 0)
)

# Fillet flange outer corners
edges_to_fillet = []
for i, edge in enumerate(flange_outer.Edges):
    if abs(edge.Curve.Direction.z) > 0.99:
        edges_to_fillet.append((i+1, corner_radius + flange_width, corner_radius + flange_width))
        
if edges_to_fillet:
    flange_outer = flange_outer.makeFillet(corner_radius + flange_width, 
                                          [flange_outer.Edges[i[0]-1] for i in edges_to_fillet])

# Create inner cutout
flange_inner = Part.makeBox(length, width, flange_thickness + 1, 
                            FreeCAD.Vector(0, 0, -0.5))

edges_to_fillet = []
for i, edge in enumerate(flange_inner.Edges):
    if abs(edge.Curve.Direction.z) > 0.99:
        edges_to_fillet.append((i+1, corner_radius, corner_radius))
        
if edges_to_fillet:
    flange_inner = flange_inner.makeFillet(corner_radius, 
                                          [flange_inner.Edges[i[0]-1] for i in edges_to_fillet])

# Create flange ring
flange_ring = flange_outer.cut(flange_inner)

# Combine with basin
basin_with_flange = hollow_basin.fuse(flange_ring)
print("✓ Top flange added: {}mm wide, {}mm thick".format(flange_width, flange_thickness))

print("\n[4/5] Adding bottom edge fillets...")

# Try to add bottom fillets
try:
    bottom_edges = []
    for edge in basin_with_flange.Edges:
        if edge.CenterOfMass.z < -(wall_depth - 5):
            if not hasattr(edge.Curve, 'Radius') or edge.Curve.Radius > 100:
                bottom_edges.append(edge)
    
    if bottom_edges[:8]:  # Try just first 8 edges
        basin_with_flange = basin_with_flange.makeFillet(bottom_fillet, bottom_edges[:8])
        print("✓ Bottom fillets added: {}mm radius".format(bottom_fillet))
except:
    print("⚠ Could not add bottom fillets (proceeding without)")

print("\n[5/5] Creating optimized mesh ({}mm holes, {}mm spacing)...".format(hole_diameter, hole_spacing))

# WORKING CORNER LOGIC (from the debug version that worked)
# Calculate hole grid
inner_length = length - 2 * wall_thickness
inner_width = width - 2 * wall_thickness
inner_radius = corner_radius - wall_thickness

# Safety margin
margin = hole_diameter / 2 + 1.0

# Grid setup
start_x = wall_thickness + margin
start_y = wall_thickness + margin
end_x = length - wall_thickness - margin
end_y = width - wall_thickness - margin

n_x = int((end_x - start_x) / hole_spacing) + 1
n_y = int((end_y - start_y) / hole_spacing) + 1

spacing_x = (end_x - start_x) / (n_x - 1) if n_x > 1 else 0
spacing_y = (end_y - start_y) / (n_y - 1) if n_y > 1 else 0

print("Grid: {} x {} = {} positions".format(n_x, n_y, n_x * n_y))

# Create holes with CORRECT corner coverage
holes = []
hole_count = 0

for i in range(n_x):
    for j in range(n_y):
        x = start_x + i * spacing_x
        y = start_y + j * spacing_y
        
        # Convert to inner coordinate system
        inner_x = x - wall_thickness
        inner_y = y - wall_thickness
        
        valid = False
        
        # Check if in main rectangle areas
        if inner_radius <= inner_x <= inner_length - inner_radius and 0 <= inner_y <= inner_width:
            valid = True
        elif 0 <= inner_x <= inner_length and inner_radius <= inner_y <= inner_width - inner_radius:
            valid = True
        else:
            # Check corner circles (THIS IS THE WORKING LOGIC)
            corners = [
                (inner_radius, inner_radius),                          # Bottom-left
                (inner_length - inner_radius, inner_radius),           # Bottom-right
                (inner_length - inner_radius, inner_width - inner_radius), # Top-right
                (inner_radius, inner_width - inner_radius)             # Top-left
            ]
            
            for cx, cy in corners:
                dist = math.sqrt((inner_x - cx)**2 + (inner_y - cy)**2)
                # Hole is valid if INSIDE the corner radius
                if dist <= inner_radius - margin + wall_thickness:
                    valid = True
                    break
        
        if valid:
            hole = Part.makeCylinder(
                hole_diameter/2,
                wall_thickness + 2,
                FreeCAD.Vector(x, y, -wall_depth - 1),
                FreeCAD.Vector(0, 0, 1)
            )
            holes.append(hole)
            hole_count += 1

print("Creating {} drainage holes (optimized from ~2000)...".format(hole_count))

# Combine holes for single cut operation
if holes:
    # Combine in batches for performance
    batch_size = 50
    combined_holes = None
    
    for i in range(0, len(holes), batch_size):
        batch = holes[i:min(i+batch_size, len(holes))]
        
        # Combine batch
        batch_combined = batch[0]
        for hole in batch[1:]:
            batch_combined = batch_combined.fuse(hole)
        
        # Add to total
        if combined_holes is None:
            combined_holes = batch_combined
        else:
            combined_holes = combined_holes.fuse(batch_combined)
        
        if i % 100 == 0:
            print("  Processed {}/{} holes...".format(min(i+batch_size, len(holes)), len(holes)))
    
    # Cut holes from basin
    print("Cutting holes from basin...")
    final_basin = basin_with_flange.cut(combined_holes)
    print("✓ Mesh bottom created: {} holes with COMPLETE corner coverage".format(hole_count))
else:
    final_basin = basin_with_flange
    print("Warning: No holes created")

# Create final object
final_obj = doc.addObject("Part::Feature", "DrainBasin_Final")
final_obj.Shape = final_basin
final_obj.Label = "Drain Basin 80mm Final (Optimized)"

# Set visualization
if FreeCAD.GuiUp:
    final_obj.ViewObject.ShapeColor = (0.3, 0.4, 0.5)
    final_obj.ViewObject.Transparency = 0
    final_obj.ViewObject.DisplayMode = "Shaded"

# Final statistics
print("\n" + "="*60)
print("✓ DRAIN BASIN COMPLETE - FINAL VERSION!")
print("="*60)

bbox = final_basin.BoundBox
volume = final_basin.Volume
mass = volume / 1000 * 1.25  # PLA density

print("\nDimensions:")
print("  Overall: {:.1f} x {:.1f} x {:.1f} mm".format(
    bbox.XMax - bbox.XMin,
    bbox.YMax - bbox.YMin, 
    abs(bbox.ZMin - bbox.ZMax)))
print("  Basin depth: {} mm".format(wall_depth))
print("  Wall thickness: {} mm".format(wall_thickness))
print("  Top flange: {} x {} mm".format(flange_width, flange_thickness))

print("\nOptimized Mesh:")
print("  Hole diameter: {} mm".format(hole_diameter))
print("  Hole spacing: {} mm".format(hole_spacing))
print("  Number of holes: {} (ALL CORNERS COVERED)".format(hole_count))

print("\n3D Printing:")
print("  Volume: {:.0f} mm³".format(volume))
print("  Estimated mass (PLA): {:.1f} g".format(mass))
print("  Estimated print time: ~{:.1f} hours".format(mass/5))

print("\n✓ Ready for STL export - will not hang!")
print("✓ All corners have drainage holes!")

# Update view
doc.recompute()
if FreeCAD.GuiUp:
    FreeCAD.Gui.activeDocument().activeView().viewAxometric()
    FreeCAD.Gui.SendMsgToActiveView("ViewFit")
