# -*- coding: utf-8 -*-
"""
FreeCad Spring Macro - Clean Version
Creates a vertical coil spring using Part.makeHelix + makePipeShell

Usage: Modify parameters below, then run macro
Result: Creates a solid 3D spring in FreeCad
"""

import FreeCAD as App
import FreeCADGui as Gui
import Part
from FreeCAD import Base

def create_spring():
    """
    Creates a vertical coil spring using proven FreeCad API methods
    Returns the created spring object or None if failed
    """
    
    # =================================================================
    # SPRING PARAMETERS - Modify these values as needed
    # =================================================================
    spring_height = 100.0    # Total height in mm
    coil_diameter = 20.0     # Diameter of coil in mm
    wire_diameter = 5.0      # Diameter of wire in mm
    pitch = 8.0              # Distance between coils in mm
    
    # Calculate derived values
    coil_radius = coil_diameter / 2.0
    wire_radius = wire_diameter / 2.0
    num_turns = spring_height / pitch
    
    print(f"Creating spring: H={spring_height}mm, Coil⌀={coil_diameter}mm, Wire⌀={wire_diameter}mm")
    print(f"Pitch={pitch}mm, Turns={num_turns:.1f}")
    
    # =================================================================
    # DOCUMENT SETUP
    # =================================================================
    if not App.ActiveDocument:
        App.newDocument("SpringDocument")
    doc = App.ActiveDocument
    
    try:
        # =============================================================
        # STEP 1: CREATE HELIX PATH
        # =============================================================
        # Creates a helical wire path that the spring will follow
        # Parameters: pitch (mm), height (mm), radius (mm)
        helix = Part.makeHelix(pitch, spring_height, coil_radius)
        
        # =============================================================
        # STEP 2: CREATE WIRE CROSS-SECTION  
        # =============================================================
        # Create circular profile that will be swept along the helix
        # The circle must be positioned and oriented correctly:
        # - Position: At helix start point (coil_radius, 0, 0)
        # - Normal: Perpendicular to helix initial direction (0, 1, 0)
        center = Base.Vector(coil_radius, 0, 0)  # Position at helix start
        normal = Base.Vector(0, 1, 0)            # Perpendicular to helix direction
        circle = Part.makeCircle(wire_radius, center, normal)
        
        # =============================================================
        # STEP 3: CREATE SPRING SOLID
        # =============================================================
        # Convert geometry to wires (required for makePipeShell)
        helix_wire = Part.Wire(helix)      # Helix path as wire
        circle_wire = Part.Wire([circle])  # Circle profile as wire
        
        # Sweep the circle along the helix to create spring
        # Parameters: [profiles], makeSolid, useFrenet
        # - makeSolid=True: Creates solid instead of surface
        # - useFrenet=True: Proper orientation along curved path
        spring_shape = helix_wire.makePipeShell([circle_wire], True, True)
        
        # =============================================================
        # STEP 4: ADD TO FREECAD DOCUMENT
        # =============================================================
        spring_obj = doc.addObject("Part::Feature", "Spring")
        spring_obj.Shape = spring_shape
        spring_obj.Label = f"Spring_H{spring_height}_D{coil_diameter}_W{wire_diameter}"
        
        # Set visual appearance
        spring_obj.ViewObject.ShapeColor = (0.8, 0.8, 1.0)  # Light blue
        
        # Update document
        doc.recompute()
        
        # =============================================================
        # STEP 5: ADJUST VIEW
        # =============================================================
        # Fit view to show complete spring in good 3D perspective
        Gui.activeDocument().activeView().fitAll()
        Gui.activeDocument().activeView().viewAxometric()
        
        print("✓ Spring created successfully!")
        return spring_obj
        
    except Exception as e:
        print(f"❌ Error: {str(e)}")
        return None

# =================================================================
# MAIN EXECUTION
# =================================================================
if __name__ == "__main__":
    spring = create_spring()
    
    if spring:
        print("\n🎉 SUCCESS: Your spring is ready!")
        print("The spring should now be visible in the 3D view.")
    else:
        print("\n💥 FAILED: Spring creation unsuccessful.")
        print("Check error messages above for details.")
