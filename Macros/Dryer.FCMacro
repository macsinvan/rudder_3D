# FreeCAD 1.1.1 Spiral Tunnel Creator - Clean PartDesign Method
# Uses proper PartDesign workflow with Additive Helix

"""
IN-LINE FILAMENT DRYER MODULE FOR 3D PRINTING
==============================================

Purpose:
--------
This module creates an active in-line filament dryer that dries 3D printing filament 
as it feeds from the spool to the printer. Unlike traditional box dryers that dry 
entire spools, this system dries only the filament that's about to be used.

Design Overview:
----------------
- Cylindrical module with a spiral path for filament to travel through
- Central hole (35mm) for heating element/hot air source
- Filament enters tangentially at bottom, exits tangentially at top
- Total path length through 10 loops maximizes drying time
- Module height: 50mm, Outer diameter: 150mm

DEVELOPMENT STRATEGY
====================
This code follows an iterative, verifiable development approach:

1. DISCRETE STEPS: Each major operation is a separate step that can be verified
2. VISUAL VERIFICATION: Each step creates visible, inspectable geometry
3. EXECUTION CONTROL: Use EXECUTE_UP_TO_STEP parameter to control how far to build
4. COMPONENT ISOLATION: Keep new additions separate wherever possible, even if less efficient
5. REFACTOR LATER: Prioritize clarity and verifiability over efficiency during development

To use:
- Set EXECUTE_UP_TO_STEP = N to build only up to step N
- Inspect each component visually before proceeding
- Components should be color-coded for easy identification
- All components remain separate until final combine step
- Each step is a point where visual check can be done

This allows debugging and refinement of individual steps without
rebuilding everything each time. Structure the code as discrete steps,
each being a verification point. We can always come back and refactor
for efficiency after verification.

Claude AI assisted development methodology:
- Work iteratively with verification at each step
- Keep additions separate for easy debugging
- Include clear step markers for visual checks
- Use parameter control for execution depth

Current Implementation Status:
------------------------------
✓ Basic spiral tunnel path (3mm diameter for 1.75mm filament)
✓ Wall thickness parameter (5mm) to prevent breakthrough
✓ Tangential entry/exit tunnels for smooth filament feeding
✓ Parametric design for easy adjustment

NEXT PHASE - Air Flow & Support System:
----------------------------------------
The design uses a removable insert system for easy threading and optimal airflow:

1. BOX CUTOUT:
   - Rectangular cut through the outer cylinder wall
   - Exposes multiple spiral loops from the outside
   - Location: Side wall of cylinder
   - Purpose: Air exit and filament access

2. RADIAL AIR HOLES:
   - Drilled from center hole outward to spiral groove
   - Direct hot air jets onto exposed filament
   - Positioned at each spiral level in cutout zone
   - Hot air path: Center → Radial holes → Over filament → Out cutout

3. REMOVABLE INSERT (Key Innovation):
   - Fits into the box cutout
   - TWO MODES:
     * Removed: Open groove for easy filament threading
     * Installed: Completes tunnel, guides filament across gap
   - Features needed:
     * Ventilation slots for air flow
     * Support bridges for filament
     * Retention clips/tabs
     * Inner surface matching spiral curve

WORKFLOW:
---------
1. Remove insert → Expose spiral groove
2. Thread filament → Lay into open groove  
3. Replace insert → Complete tunnel
4. Activate heating → Dry filament during printing

Key Design Challenges:
----------------------
- Balance airflow vs filament support
- Ensure easy threading while maintaining guidance
- Optimize hole size/spacing for drying efficiency
- Design insert retention mechanism

Parameters:
-----------
- OUTER_DIAMETER: 150mm - Module outer diameter
- CENTER_HOLE_DIAMETER: 35mm - Central heating core
- MODULE_HEIGHT: 50mm - Total height
- NUM_LOOPS: 10 - Number of spiral loops
- TUNNEL_DIAMETER: 3mm - Tunnel for 1.75mm filament + clearance
- WALL_THICKNESS: 5mm - Minimum wall thickness on all sides

TODO List:
----------
[ ] Implement box cutout in cylinder wall
[ ] Add air inlet chute
[ ] Add radial air holes from center to spiral
[ ] Design removable insert piece
[ ] Add insert retention features
[ ] Create ventilation pattern in insert
[ ] Add support bridges in insert
[ ] Test threading ease and airflow patterns

Usage:
------
Run this script in FreeCAD to generate the filament dryer module.
The module can be 3D printed and integrated with a heating element
to provide active drying as filament feeds to the printer.
"""

import FreeCAD
import Part
import Sketcher
import PartDesign
import math

# Handle FreeCADGui import safely
try:
    import FreeCADGui
    GUI_AVAILABLE = True
except ImportError:
    GUI_AVAILABLE = False

# ============================================================================
# EXECUTION CONTROL - CHANGE THIS TO CONTROL BUILD STEPS
# ============================================================================
EXECUTE_UP_TO_STEP = 999  # Set to step number to pause at that step
                          # 1 = Spiral body only
                          # 2 = Add entry/exit tunnels (coil extensions)
                          # 3 = Add main cylinder  
                          # 4 = Add cutout box
                          # 7 = Final assembly (combine & cut)
                          # 999 = Build everything (default)
# ============================================================================

def create_spiral_tunnel_module():
    """
    Create filament dryer module using proper PartDesign Additive Helix method
    """
    
    # Base Parameters
    OUTER_DIAMETER = 150.0      # mm - module outer diameter
    CENTER_HOLE_DIAMETER = 35.0 # mm - central heating core
    MODULE_HEIGHT = 50.0        # mm - module height
    NUM_LOOPS = 10             # number of spiral loops
    TUNNEL_DIAMETER = 3.0      # mm - tunnel for 1.75mm filament + clearance
    WALL_THICKNESS = 5.0       # mm - minimum wall thickness on all sides
    
    # Calculated parameters - all in one place
    SPIRAL_RADIUS = (OUTER_DIAMETER/2) - WALL_THICKNESS - (TUNNEL_DIAMETER/2)
    spiral_height = MODULE_HEIGHT - (2 * WALL_THICKNESS) - TUNNEL_DIAMETER
    pitch = spiral_height / NUM_LOOPS  # Height per loop
    z_offset = WALL_THICKNESS + (TUNNEL_DIAMETER/2)  # Start spiral center up from bottom
    
    # Create parameters dictionary for consistent passing
    params = {
        'OUTER_DIAMETER': OUTER_DIAMETER,
        'CENTER_HOLE_DIAMETER': CENTER_HOLE_DIAMETER,
        'MODULE_HEIGHT': MODULE_HEIGHT,
        'NUM_LOOPS': NUM_LOOPS,
        'TUNNEL_DIAMETER': TUNNEL_DIAMETER,
        'WALL_THICKNESS': WALL_THICKNESS,
        'SPIRAL_RADIUS': SPIRAL_RADIUS,
        'spiral_height': spiral_height,
        'pitch': pitch,
        'z_offset': z_offset
    }
    
    print(f"FreeCAD Spiral Tunnel Creator v2.1")
    print(f"Creating spiral tunnel module using PartDesign Additive Helix:")
    print(f"  Tunnel diameter: {TUNNEL_DIAMETER}mm")
    print(f"  Wall thickness: {WALL_THICKNESS}mm")
    print(f"  Spiral radius: {SPIRAL_RADIUS}mm") 
    print(f"  Spiral height: {spiral_height}mm")
    print(f"  Pitch: {pitch:.1f}mm")
    print(f"  Total height: {MODULE_HEIGHT}mm")
    print(f"  Turns: {NUM_LOOPS}")
    
    # Create document
    try:
        doc = FreeCAD.getDocument("FilamentDryer")
        # Clear existing document - commented out for development
        # for obj in doc.Objects:
        #     doc.removeObject(obj.Name)
    except:
        doc = FreeCAD.newDocument("FilamentDryer")
    
    # Build sequence - centralized calls
    current_step = 0
    components_created = []
    
    # Step 1: Create spiral tunnel body
    current_step += 1
    if current_step <= EXECUTE_UP_TO_STEP:
        print(f"\n{'='*60}")
        print(f"STEP {current_step}: Creating spiral tunnel body")
        print(f"{'='*60}")
        body, helix_created = create_spiral_body(doc, params)
        components_created.append("Spiral Body")
    else:
        print(f"\n⏸ PAUSED: Execution stopped before step {current_step} (EXECUTE_UP_TO_STEP = {EXECUTE_UP_TO_STEP})")
        body = None
        helix_created = False
    
    # Step 2: Create entry and exit tunnels (coil extensions)
    current_step += 1
    if current_step <= EXECUTE_UP_TO_STEP:
        print(f"\n{'='*60}")
        print(f"STEP {current_step}: Creating entry/exit tunnels (coil extensions)")
        print(f"{'='*60}")
        entry_tunnel, exit_tunnel = create_entry_exit_tunnels(doc, params)
        components_created.append("Entry/Exit Tunnels")
    else:
        print(f"\n⏸ PAUSED: Execution stopped before step {current_step} (EXECUTE_UP_TO_STEP = {EXECUTE_UP_TO_STEP})")
        entry_tunnel = None
        exit_tunnel = None
    
    # Step 3: Create main cylinder
    current_step += 1
    if current_step <= EXECUTE_UP_TO_STEP:
        print(f"\n{'='*60}")
        print(f"STEP {current_step}: Creating main cylinder")
        print(f"{'='*60}")
        main_shape = create_main_cylinder(doc, params)
        components_created.append("Main Cylinder")
    else:
        print(f"\n⏸ PAUSED: Execution stopped before step {current_step} (EXECUTE_UP_TO_STEP = {EXECUTE_UP_TO_STEP})")
        main_shape = None
    
    # Step 4: Create cutout box
    current_step += 1
    if current_step <= EXECUTE_UP_TO_STEP:
        print(f"\n{'='*60}")
        print(f"STEP {current_step}: Creating cutout box")
        print(f"{'='*60}")
        cutout_box = create_cutout_box(doc, params)
        components_created.append("Cutout Box")
    else:
        print(f"\n⏸ PAUSED: Execution stopped before step {current_step} (EXECUTE_UP_TO_STEP = {EXECUTE_UP_TO_STEP})")
        cutout_box = None
    
    # Step 7: Combine and cut everything
    current_step += 3
    if current_step <= EXECUTE_UP_TO_STEP:
        print(f"\n{'='*60}")
        print(f"STEP {current_step}: Final assembly - combining and cutting")
        print(f"{'='*60}")
        # Only combine if we have all necessary components
        if body and main_shape:
            final_obj = combine_and_cut(doc, body, helix_created, main_shape, cutout_box, 
                                       entry_tunnel, exit_tunnel, params)
            # Hide individual components after combining
            for obj in doc.Objects:
                if obj.Name != "FinalModule":  # Hide all intermediate components
                    obj.ViewObject.Visibility = False
            components_created.append("Final Assembly")
        else:
            final_obj = None
            print("  ⚠ Cannot perform final assembly - missing components")
    else:
        print(f"\n⏸ PAUSED: Execution stopped before step {current_step} (EXECUTE_UP_TO_STEP = {EXECUTE_UP_TO_STEP})")
        final_obj = None
    
    # Final cleanup
    doc.recompute()
    if GUI_AVAILABLE:
        try:
            FreeCADGui.SendMsgToActiveView("ViewFit")
            FreeCADGui.activeDocument().activeView().viewAxonometric()
        except:
            pass
    
    # Report execution status
    print("\n" + "="*60)
    if EXECUTE_UP_TO_STEP == 999:
        print("✅ FULL BUILD COMPLETE - All steps executed")
    else:
        print(f"⏸ PAUSED BUILD - Executed up to step {min(EXECUTE_UP_TO_STEP, current_step-1)}")
    print("="*60)
    
    print("\n📋 Components created:")
    for i, component in enumerate(components_created, 1):
        print(f"  {i}. {component}")
    
    if EXECUTE_UP_TO_STEP < 999:
        print(f"\n💡 To continue: Change EXECUTE_UP_TO_STEP to a higher value and re-run")
        print(f"   Current setting: EXECUTE_UP_TO_STEP = {EXECUTE_UP_TO_STEP}")
    
    print("\n✓ Module creation complete!")
    if helix_created:
        print("  - Spiral tunnel successfully integrated")
    elif EXECUTE_UP_TO_STEP >= 1:
        print("  - Main cylinder created (tunnel creation failed)")
    print(f"  - Dimensions: {params['OUTER_DIAMETER']}mm × {params['MODULE_HEIGHT']}mm")
    print(f"  - Center hole: {params['CENTER_HOLE_DIAMETER']}mm")
    
    # Return the final object if it was created, otherwise return the last created component
    if EXECUTE_UP_TO_STEP >= 7 and final_obj:
        return final_obj
    else:
        # Return something valid to prevent "Failed to create module" message
        return doc.Objects[-1] if doc.Objects else None


def create_spiral_body(doc, params):
    """Create the spiral tunnel body using PartDesign"""
    
    # Extract parameters
    SPIRAL_RADIUS = params['SPIRAL_RADIUS']
    TUNNEL_DIAMETER = params['TUNNEL_DIAMETER']
    spiral_height = params['spiral_height']
    pitch = params['pitch']
    z_offset = params['z_offset']
    NUM_LOOPS = params['NUM_LOOPS']
    
    # Create PartDesign Body for tunnel
    body = doc.addObject('PartDesign::Body', 'Spiral_Body')
    
    # Create sketch for circular profile
    sketch = body.newObject('Sketcher::SketchObject', 'Spiral_Profile')
    
    # Position the sketch at the bottom with wall thickness offset
    sketch.Placement = FreeCAD.Placement(
        FreeCAD.Vector(0, 0, z_offset),
        FreeCAD.Rotation(0, 0, 0)
    )
    
    # The profile should be a circle at the spiral radius on the XY plane
    # For a helix around Z-axis, profile should be offset from origin
    circle = sketch.addGeometry(Part.Circle(
        FreeCAD.Vector(SPIRAL_RADIUS, 0, 0),  # Center at spiral radius
        FreeCAD.Vector(0, 0, 1),              # Normal to XY plane
        TUNNEL_DIAMETER/2                      # Radius of tunnel
    ), False)  # False = not construction geometry
    
    # Add constraints to fully define the circle
    sketch.addConstraint(Sketcher.Constraint('Radius', circle, TUNNEL_DIAMETER/2))
    
    # Constrain the center point position
    center_point = sketch.getPoint(circle, 3)  # 3 = center point
    sketch.addConstraint(Sketcher.Constraint('DistanceX', -1, 1, circle, 3, SPIRAL_RADIUS))
    sketch.addConstraint(Sketcher.Constraint('DistanceY', -1, 1, circle, 3, 0))
    
    doc.recompute()
    print("✓ Created circular profile sketch at spiral radius")
    
    # Create Additive Helix
    helix_created = False
    try:
        helix = body.newObject("PartDesign::AdditiveHelix", "Spiral_Helix")
        helix.Profile = sketch
        
        # Set helix parameters
        helix.Mode = 0  # 0 = pitch-height mode
        helix.Pitch = pitch
        helix.Height = spiral_height  # Use reduced height to maintain wall thickness
        helix.Turns = NUM_LOOPS
        helix.LeftHanded = False
        helix.Reversed = False
        
        # Set reference axis to Z-axis
        helix.ReferenceAxis = (body.Origin.OriginFeatures[2], [''])  # Z-axis
        
        doc.recompute()
        
        # Check if helix created properly
        if hasattr(helix, 'Shape') and helix.Shape.isValid():
            print("✓ Created spiral tunnel using PartDesign Additive Helix")
            helix_created = True
            
            # Set visualization
            if hasattr(helix, 'ViewObject'):
                helix.ViewObject.ShapeColor = (1.0, 0.0, 1.0)  # Magenta
                helix.ViewObject.Transparency = 30
        else:
            print("❌ Helix shape is invalid")
            
    except Exception as e:
        print(f"❌ Additive Helix failed: {e}")
    
    return body, helix_created


def create_main_cylinder(doc, params):
    """Create the main cylinder with center hole - preserves bottom wall thickness"""
    
    # Extract parameters
    OUTER_DIAMETER = params['OUTER_DIAMETER']
    MODULE_HEIGHT = params['MODULE_HEIGHT']
    CENTER_HOLE_DIAMETER = params['CENTER_HOLE_DIAMETER']
    WALL_THICKNESS = params['WALL_THICKNESS']
    
    # Position cylinder centered on origin
    outer_cylinder = Part.makeCylinder(
        OUTER_DIAMETER/2, 
        MODULE_HEIGHT,
        FreeCAD.Vector(0, 0, 0)
    )
    
    # Create center hole that preserves bottom wall thickness
    center_hole = Part.makeCylinder(
        CENTER_HOLE_DIAMETER/2, 
        MODULE_HEIGHT - WALL_THICKNESS,        # Preserve bottom wall
        FreeCAD.Vector(0, 0, WALL_THICKNESS)   # Start above bottom wall
    )
    
    main_shape = outer_cylinder.cut(center_hole)
    
    # Create visible object for inspection
    main_obj = doc.addObject("Part::Feature", "Main_Cylinder")
    main_obj.Shape = main_shape
    main_obj.ViewObject.ShapeColor = (0.5, 0.5, 0.8)
    main_obj.ViewObject.Transparency = 70
    
    print(f"✓ Created main cylinder with center hole")
    print(f"  - Outer: ⌀{OUTER_DIAMETER}mm × {MODULE_HEIGHT}mm")
    print(f"  - Center hole: ⌀{CENTER_HOLE_DIAMETER}mm × {MODULE_HEIGHT - WALL_THICKNESS}mm")
    print(f"  - Bottom wall preserved: {WALL_THICKNESS}mm thick")
    
    return main_shape


def create_cutout_box(doc, params):
    """Create trapezoidal cutout for radial air flow"""
    
    # Extract parameters
    spiral_height = params['spiral_height']
    z_offset = params['z_offset']
    WALL_THICKNESS = params['WALL_THICKNESS']
    OUTER_DIAMETER = params['OUTER_DIAMETER']
    CENTER_HOLE_DIAMETER = params['CENTER_HOLE_DIAMETER']
    
    # Create trapezoidal shape for radial air flow
    inner_radius = CENTER_HOLE_DIAMETER / 2
    outer_radius = OUTER_DIAMETER / 2
    inner_width = CENTER_HOLE_DIAMETER  # Width at inner edge
    outer_width = 1.5 * CENTER_HOLE_DIAMETER  # Width at outer edge
    
    # Create trapezoidal profile points - starts at centerline (X=0) and expands outward
    points = [
        FreeCAD.Vector(0, inner_width/2, 0),               # Centerline, top
        FreeCAD.Vector(outer_radius, outer_width/2, 0),    # Outer cylinder edge, top
        FreeCAD.Vector(outer_radius, -outer_width/2, 0),   # Outer cylinder edge, bottom
        FreeCAD.Vector(0, -inner_width/2, 0),              # Centerline, bottom
        FreeCAD.Vector(0, inner_width/2, 0)                # Close the shape
    ]
    
    # Create the trapezoidal face
    edges = []
    for i in range(len(points)-1):
        edges.append(Part.makeLine(points[i], points[i+1]))
    
    wire = Part.Wire(edges)
    face = Part.Face(wire)
    
    # Extrude the trapezoid to create 3D shape
    cutout_trapezoid = face.extrude(FreeCAD.Vector(0, 0, spiral_height))
    
    # Position trapezoid on the back side (negative X) and align with spiral section
    cutout_trapezoid.Placement = FreeCAD.Placement(
        FreeCAD.Vector(0, 0, z_offset),
        FreeCAD.Rotation(FreeCAD.Vector(0, 0, 1), 180)  # Rotate 180° to face negative X
    )
    
    # Create visible object for inspection
    cutout_obj = doc.addObject("Part::Feature", "Airflow_Cutout")
    cutout_obj.Shape = cutout_trapezoid
    cutout_obj.ViewObject.ShapeColor = (1.0, 1.0, 0.0)
    cutout_obj.ViewObject.Transparency = 50
    
    print(f"✓ Created trapezoidal cutout for radial air flow:")
    print(f"  Inner width: {inner_width:.1f}mm, Outer width: {outer_width:.1f}mm")
    print(f"  Height: {spiral_height:.1f}mm, Depth: {outer_radius - inner_radius:.1f}mm")
    
    return cutout_trapezoid


def create_entry_exit_tunnels(doc, params):
    """Create tangential entry and exit tunnels"""
    
    # Extract parameters
    SPIRAL_RADIUS = params['SPIRAL_RADIUS']
    TUNNEL_DIAMETER = params['TUNNEL_DIAMETER']
    OUTER_DIAMETER = params['OUTER_DIAMETER']
    pitch = params['pitch']
    z_offset = params['z_offset']
    spiral_height = params['spiral_height']
    NUM_LOOPS = params['NUM_LOOPS']
    
    def calculate_tangent_vector(angle, pitch, radius):
        """Helper function to calculate normalized tangent vector at given angle"""
        tangent_x = -math.sin(angle)  # Derivative of cos
        tangent_y = math.cos(angle)   # Derivative of sin
        tangent_z = pitch / (2 * math.pi * radius)  # Vertical component based on pitch
        return FreeCAD.Vector(tangent_x, tangent_y, tangent_z).normalize()
    
    # Calculate required tunnel length to clear the cylinder
    clearance_length = math.sqrt((OUTER_DIAMETER/2)**2 - (SPIRAL_RADIUS)**2) * 1.2  # 1.2 safety factor
    tunnel_length = clearance_length + 20.0  # Add 20mm for obvious exit
    
    # Calculate entry point (start of helix)
    entry_angle = 0
    entry_x = SPIRAL_RADIUS * math.cos(entry_angle)
    entry_y = SPIRAL_RADIUS * math.sin(entry_angle)
    entry_z = z_offset
    
    # Entry tunnel - tangential to spiral at start
    entry_tangent = calculate_tangent_vector(entry_angle, pitch, SPIRAL_RADIUS)
    
    # Create entry tunnel extending backwards from entry point
    entry_tunnel = Part.makeCylinder(
        TUNNEL_DIAMETER/2,
        tunnel_length,
        FreeCAD.Vector(entry_x - entry_tangent.x * tunnel_length,
                      entry_y - entry_tangent.y * tunnel_length,
                      entry_z - entry_tangent.z * tunnel_length),
        entry_tangent
    )
    
    # Calculate exit point (end of helix)
    exit_angle = 2 * math.pi * NUM_LOOPS  # Total rotation in radians
    exit_x = SPIRAL_RADIUS * math.cos(exit_angle)
    exit_y = SPIRAL_RADIUS * math.sin(exit_angle)
    exit_z = z_offset + spiral_height
    
    # Exit tunnel - tangential to spiral at end
    exit_tangent = calculate_tangent_vector(exit_angle, pitch, SPIRAL_RADIUS)
    
    # Create exit tunnel extending forward from exit point
    exit_tunnel = Part.makeCylinder(
        TUNNEL_DIAMETER/2,
        tunnel_length,
        FreeCAD.Vector(exit_x, exit_y, exit_z),
        exit_tangent
    )
    
    # Create visible objects for inspection
    entry_obj = doc.addObject("Part::Feature", "Tunnel_Entry")
    entry_obj.Shape = entry_tunnel
    entry_obj.ViewObject.ShapeColor = (0.0, 1.0, 0.0)
    entry_obj.ViewObject.Transparency = 30
    
    exit_obj = doc.addObject("Part::Feature", "Tunnel_Exit")
    exit_obj.Shape = exit_tunnel
    exit_obj.ViewObject.ShapeColor = (1.0, 0.0, 0.0)
    exit_obj.ViewObject.Transparency = 30
    
    print(f"✓ Created tangential entry tunnel at angle 0° at height {entry_z:.1f}mm")
    print(f"✓ Created tangential exit tunnel at angle {math.degrees(exit_angle):.1f}° at height {exit_z:.1f}mm")
    print(f"  Calculated clearance: {clearance_length:.1f}mm + 20mm extension = {tunnel_length:.1f}mm total")
    
    return entry_tunnel, exit_tunnel


def combine_and_cut(doc, body, helix_created, main_shape, cutout_box, 
                    entry_tunnel, exit_tunnel, params):
    """Combine all elements and perform final cuts"""
    
    if helix_created and body.Shape.isValid():
        try:
            # Combine helix tunnel with entry and exit tunnels
            tunnel_system = body.Shape.fuse([entry_tunnel, exit_tunnel])
            
            # Cut the complete tunnel system from main cylinder
            final_shape = main_shape.cut(tunnel_system)
            
            # Now cut the airflow features
            final_shape = final_shape.cut(cutout_box)
            
            final_obj = doc.addObject("Part::Feature", "FinalModule")
            final_obj.Shape = final_shape
            final_obj.Label = "Filament Dryer Module"
            
            # Set visualization
            if hasattr(final_obj, 'ViewObject'):
                final_obj.ViewObject.Transparency = 50
                final_obj.ViewObject.ShapeColor = (0.8, 0.8, 0.9)
            
            # Hide the body since we have the final part
            body.ViewObject.Visibility = False
            
            print("✓ Successfully cut spiral tunnel with entry/exit ports from main cylinder")
            
        except Exception as e:
            print(f"❌ Cut operation failed: {e}")
            print("Creating main cylinder without tunnel")
            
            final_obj = doc.addObject("Part::Feature", "FinalModule_NoTunnel")
            final_obj.Shape = main_shape
            final_obj.Label = "Main Cylinder (No Tunnel)"
    else:
        # If helix failed, just create the main cylinder
        print("Creating main cylinder without tunnel")
        
        final_obj = doc.addObject("Part::Feature", "FinalModule_NoTunnel")
        final_obj.Shape = main_shape
        final_obj.Label = "Main Cylinder (No Tunnel)"
        
        if hasattr(final_obj, 'ViewObject'):
            final_obj.ViewObject.Transparency = 50
            final_obj.ViewObject.ShapeColor = (0.8, 0.8, 0.9)
    
    return final_obj


# Main execution
if __name__ == "__main__":
    module = create_spiral_tunnel_module()
    # All success/error messages are already handled within the main function
